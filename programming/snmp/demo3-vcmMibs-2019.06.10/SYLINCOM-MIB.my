--
-- SYLINCOM-MIB.my
-- MIB generated by MG-SOFT Visual MIB Builder Version 6.0  Build 88
-- Monday, June 10, 2019 at 11:35:58
--

--  SYLINCOM-MIB.mib
-- MIB generated by MG-SOFT Visual MIB Builder Version 6.0  Build 88
-- Wednesday, June 05, 2019 at 17:23:56
-- 

SYLINCOM-MIB DEFINITIONS ::= BEGIN
 
		IMPORTS
			enterprises, IpAddress, Integer32, Unsigned32, Counter64, 
			OBJECT-TYPE, MODULE-IDENTITY, NOTIFICATION-TYPE			
				FROM SNMPv2-SMI			
			DisplayString, DateAndTime, MacAddress, RowStatus, TruthValue, 
			TEXTUAL-CONVENTION			
				FROM SNMPv2-TC;
	
	
		-- 1.3.6.1.4.1.1.2
		jtsranMIB MODULE-IDENTITY 
			LAST-UPDATED "201905170954Z"		-- May 17, 2019 at 09:54 GMT
			ORGANIZATION 
				"Organization."
			CONTACT-INFO 
				"Contact-info."
			DESCRIPTION 
				"Description."
			::= { sylincom 2 }

		
	
--
-- Textual conventions
--
	
		JtSranAlarmSeqNum ::= TEXTUAL-CONVENTION
			STATUS current
			DESCRIPTION 
				"
				告警/事件序号，告警和事件各自编码，从1开始，按顺序自增。  "
			SYNTAX Unsigned32 (1..1729917383)

		JtSranAlarmSrc ::= TEXTUAL-CONVENTION
			STATUS current
			DESCRIPTION 
				"
				告警/事件的源，总共8个字节，各字节含义根据告警源定义。
				
				设备告警:
				    第一个字节为设备ID，其余字节无效
				
				板卡告警：
				    第一个字节为设备ID，第二个字节为槽位号，其余字节无效  "
			SYNTAX OCTET STRING (SIZE (8))

		JtSranAlarmPriority ::= TEXTUAL-CONVENTION
			STATUS current
			DESCRIPTION 
				"
				告警优先级定义
				
				1-优先级高
				0-优先级低
				"
			SYNTAX INTEGER
				{
				low(0),
				high(1)
				}

		JtSranAlarmLevel ::= TEXTUAL-CONVENTION
			STATUS current
			DESCRIPTION 
				"
				告警级别定义
				
				1   ///< VITAL 紧急告警
				2   ///< MAJOR 重要告警
				3   ///< MINOR 错误消息
				4   ///< WARNING 警告，一般告警
				5   ///< CLEAR 告警清除   
				6   ///< EVENT-NOTICE，通知消息  "
			SYNTAX INTEGER
				{
				null(0),
				vital(1),
				major(2),
				minor(3),
				warning(4),
				clear(5),
				event-notice(6)
				}

--  1.3.6.1.4.1.1.2
-- May 17, 2019 at 09:54 GMT
-- 
-- Textual conventions
-- 
		JtSranDeviceIndex ::= TEXTUAL-CONVENTION
			STATUS current
			DESCRIPTION 
				"Description."
			SYNTAX Unsigned32

		JtSranSlotIndex ::= TEXTUAL-CONVENTION
			STATUS current
			DESCRIPTION 
				"Description."
			SYNTAX Unsigned32

		JtSranCellMode ::= TEXTUAL-CONVENTION
			STATUS current
			DESCRIPTION 
				"Description."
			SYNTAX INTEGER
				{
				gsm(1),
				gmr(2),
				wcdma(3),
				tdscdma(4),
				tddlte(5),
				fddlte(6)
				}

		JtSranCellType ::= TEXTUAL-CONVENTION
			STATUS current
			DESCRIPTION 
				"Description."
			SYNTAX INTEGER
				{
				virtual(1),
				simulate(2)
				}

		JtSranCellRole ::= TEXTUAL-CONVENTION
			STATUS current
			DESCRIPTION 
				"Description."
			SYNTAX INTEGER
				{
				unify(1),
				bbu(2),
				rru(3)
				}

	
--
-- Node definitions
--
	
--  Node definitions
-- 
-- 1.3.6.1.4.1.1
		-- 1.3.6.1.4.1.1
		sylincom OBJECT IDENTIFIER ::= { enterprises 1 }

		
--  1.3.6.1.4.1.1.1
		-- 1.3.6.1.4.1.1.1
		common OBJECT IDENTIFIER ::= { sylincom 1 }

		
--  1.3.6.1.4.1.1.1.1
		-- 1.3.6.1.4.1.1.1.1
		systemObject OBJECT IDENTIFIER ::= { common 1 }

		
--  1.3.6.1.4.1.1.1.1.1
		-- 1.3.6.1.4.1.1.1.1.1
		productType OBJECT-TYPE
			SYNTAX Integer32
			MAX-ACCESS read-only
			STATUS current
			DESCRIPTION
				"Description."
			::= { systemObject 1 }

		
--  1.3.6.1.4.1.1.1.1.2
		-- 1.3.6.1.4.1.1.1.1.2
		productName OBJECT-TYPE
			SYNTAX DisplayString
			MAX-ACCESS read-only
			STATUS current
			DESCRIPTION
				"Description."
			::= { systemObject 2 }

		
--  1.3.6.1.4.1.1.2.1
		-- 1.3.6.1.4.1.1.2.1
		boardMgmtGroup OBJECT IDENTIFIER ::= { jtsranMIB 1 }

		
--  1.3.6.1.4.1.1.2.2
		-- 1.3.6.1.4.1.1.2.2
		cellMgmtGroup OBJECT IDENTIFIER ::= { jtsranMIB 2 }

		
		-- 1.3.6.1.4.1.1.2.2.1
		cellMgmtConfigInfoTable OBJECT-TYPE
			SYNTAX SEQUENCE OF CellMgmtConfigInfoEntry
			MAX-ACCESS not-accessible
			STATUS current
			DESCRIPTION
				"Description."
			::= { cellMgmtGroup 1 }

		
		-- 1.3.6.1.4.1.1.2.2.1.1
		cellMgmtConfigInfoEntry OBJECT-TYPE
			SYNTAX CellMgmtConfigInfoEntry
			MAX-ACCESS not-accessible
			STATUS current
			DESCRIPTION
				"Description."
			INDEX { cellMgmtConfigInfoCellGlobalID }
			::= { cellMgmtConfigInfoTable 1 }

		
		CellMgmtConfigInfoEntry ::=
			SEQUENCE { 
				cellMgmtConfigInfoCellGlobalID
					Integer32,
				cellMgmtConfigInfoCellDescribe
					DisplayString,
				cellMgmtConfigInfoCellMode
					JtSranCellMode,
				cellMgmtConfigInfoCellType
					JtSranCellType,
				cellMgmtConfigInfoCellRole
					JtSranCellRole,
				cellMgmtConfigInfoRRUSN
					OCTET STRING,
				cellMgmtConfigInfoRRUID
					Integer32,
				cellMgmtConfigInfoRRUIP
					IpAddress,
				cellMgmtConfigInfoRRUPort
					Integer32,
				cellMgmtConfigInfoPowerFactor
					Integer32,
				cellMgmtConfigInfoBBUIP
					IpAddress,
				cellMgmtConfigInfoBBUPort
					Integer32,
				cellMgmtConfigInfoCellPerfOnOff
					TruthValue,
				cellMgmtConfigInfoRowStatus
					RowStatus
			 }

-- As index of table "cellMgmtConfigInfoTable", The Global_ID is unique in the network internet.
-- 
		-- 1.3.6.1.4.1.1.2.2.1.1.1
		cellMgmtConfigInfoCellGlobalID OBJECT-TYPE
			SYNTAX Integer32 (1..65535)
			MAX-ACCESS not-accessible
			STATUS current
			DESCRIPTION
				"Description. Global ID of cells"
			::= { cellMgmtConfigInfoEntry 1 }

		
		-- 1.3.6.1.4.1.1.2.2.1.1.2
		cellMgmtConfigInfoCellDescribe OBJECT-TYPE
			SYNTAX DisplayString
			MAX-ACCESS read-create
			STATUS current
			DESCRIPTION
				"Description. The description of cell."
			::= { cellMgmtConfigInfoEntry 2 }

		
		-- 1.3.6.1.4.1.1.2.2.1.1.3
		cellMgmtConfigInfoCellMode OBJECT-TYPE
			SYNTAX JtSranCellMode
			MAX-ACCESS read-create
			STATUS current
			DESCRIPTION
				"Description. Cell Mode"
			::= { cellMgmtConfigInfoEntry 3 }

		
		-- 1.3.6.1.4.1.1.2.2.1.1.4
		cellMgmtConfigInfoCellType OBJECT-TYPE
			SYNTAX JtSranCellType
			MAX-ACCESS read-create
			STATUS current
			DESCRIPTION
				"Description. Cell Type"
			::= { cellMgmtConfigInfoEntry 4 }

		
		-- 1.3.6.1.4.1.1.2.2.1.1.5
		cellMgmtConfigInfoCellRole OBJECT-TYPE
			SYNTAX JtSranCellRole
			MAX-ACCESS read-create
			STATUS current
			DESCRIPTION
				"Description. Cell Role"
			::= { cellMgmtConfigInfoEntry 5 }

		
		-- 1.3.6.1.4.1.1.2.2.1.1.6
		cellMgmtConfigInfoRRUSN OBJECT-TYPE
			SYNTAX OCTET STRING
			MAX-ACCESS read-create
			STATUS current
			DESCRIPTION
				"Description. RRU SN"
			::= { cellMgmtConfigInfoEntry 6 }

		
		-- 1.3.6.1.4.1.1.2.2.1.1.7
		cellMgmtConfigInfoRRUID OBJECT-TYPE
			SYNTAX Integer32
			MAX-ACCESS read-create
			STATUS current
			DESCRIPTION
				"Description. RRU ID, UINT32"
			::= { cellMgmtConfigInfoEntry 7 }

		
		-- 1.3.6.1.4.1.1.2.2.1.1.8
		cellMgmtConfigInfoRRUIP OBJECT-TYPE
			SYNTAX IpAddress
			MAX-ACCESS read-create
			STATUS current
			DESCRIPTION
				"Description. RRU IP :string"
			::= { cellMgmtConfigInfoEntry 8 }

		
		-- 1.3.6.1.4.1.1.2.2.1.1.9
		cellMgmtConfigInfoRRUPort OBJECT-TYPE
			SYNTAX Integer32
			MAX-ACCESS read-create
			STATUS current
			DESCRIPTION
				"Description. RRU Port : default 31001"
			::= { cellMgmtConfigInfoEntry 9 }

		
		-- 1.3.6.1.4.1.1.2.2.1.1.10
		cellMgmtConfigInfoPowerFactor OBJECT-TYPE
			SYNTAX Integer32
			MAX-ACCESS read-create
			STATUS current
			DESCRIPTION
				"Description. RRU cpri PowerFactor"
			::= { cellMgmtConfigInfoEntry 10 }

		
		-- 1.3.6.1.4.1.1.2.2.1.1.11
		cellMgmtConfigInfoBBUIP OBJECT-TYPE
			SYNTAX IpAddress
			MAX-ACCESS read-create
			STATUS current
			DESCRIPTION
				"Description. BBU IP : "
			::= { cellMgmtConfigInfoEntry 11 }

		
		-- 1.3.6.1.4.1.1.2.2.1.1.12
		cellMgmtConfigInfoBBUPort OBJECT-TYPE
			SYNTAX Integer32
			MAX-ACCESS read-create
			STATUS current
			DESCRIPTION
				"Description. BBU port : default 31001"
			::= { cellMgmtConfigInfoEntry 12 }

		
		-- 1.3.6.1.4.1.1.2.2.1.1.13
		cellMgmtConfigInfoCellPerfOnOff OBJECT-TYPE
			SYNTAX TruthValue
			MAX-ACCESS read-create
			STATUS current
			DESCRIPTION
				"Description. Cell's performance turn on/off"
			::= { cellMgmtConfigInfoEntry 13 }

		
		-- 1.3.6.1.4.1.1.2.2.1.1.14
		cellMgmtConfigInfoRowStatus OBJECT-TYPE
			SYNTAX RowStatus
			MAX-ACCESS read-create
			STATUS current
			DESCRIPTION
				"Description. Row status"
			::= { cellMgmtConfigInfoEntry 14 }

		
--  1.3.6.1.4.1.1.2.3
		-- 1.3.6.1.4.1.1.2.3
		rruMgmtGroup OBJECT IDENTIFIER ::= { jtsranMIB 3 }

		
--  1.3.6.1.4.1.1.2.4
		-- 1.3.6.1.4.1.1.2.4
		performanceInfoGroup OBJECT IDENTIFIER ::= { jtsranMIB 4 }

		
		-- 1.3.6.1.4.1.1.2.4.1
		cellPerfInfoTable OBJECT-TYPE
			SYNTAX SEQUENCE OF CellPerfInfoEntry
			MAX-ACCESS not-accessible
			STATUS current
			DESCRIPTION
				"Description."
			::= { performanceInfoGroup 1 }

		
		-- 1.3.6.1.4.1.1.2.4.1.1
		cellPerfInfoEntry OBJECT-TYPE
			SYNTAX CellPerfInfoEntry
			MAX-ACCESS not-accessible
			STATUS current
			DESCRIPTION
				"Description."
			INDEX { cellPerfInfoCellGlobalID }
			::= { cellPerfInfoTable 1 }

		
		CellPerfInfoEntry ::=
			SEQUENCE { 
				cellPerfInfoCellGlobalID
					Integer32,
				cellPerfInfoPhyULThroughtPut
					Integer32,
				cellPerfInfoPhyDLThroughtPut
					Integer32,
				cellPerfInfoPhySNMin
					Integer32,
				cellPerfInfoPhySNMax
					Integer32,
				cellPerfInfoPhyULVol
					Counter64,
				cellPerfInfoPhyDLVol
					Counter64,
				cellPerfInfoMacULRate
					Counter64,
				cellPerfInfoMacDLRate
					Counter64,
				cellPerfInfoRlcULRate
					Counter64,
				cellPerfInfoRlcDLRate
					Counter64,
				cellPerfInfoRlcBufData
					Integer32,
				cellPerfInfoPdcpULRate
					Counter64,
				cellPerfInfoPdcpDLRate
					Counter64,
				cellPerfInfoErrBlkRate
					Integer32,
				cellPerfInfoBandwidthOccupancy
					Integer32,
				cellPerfInfoUEOns
					Integer32,
				cellPerfInfoUEOffs
					Integer32,
				cellPerfInfoUEAccessSuccRate
					Integer32
			 }

		-- 1.3.6.1.4.1.1.2.4.1.1.1
		cellPerfInfoCellGlobalID OBJECT-TYPE
			SYNTAX Integer32 (1..65535)
			MAX-ACCESS not-accessible
			STATUS current
			DESCRIPTION
				"Description. Cell's Global ID, it's unique."
			::= { cellPerfInfoEntry 1 }

		
		-- 1.3.6.1.4.1.1.2.4.1.1.2
		cellPerfInfoPhyULThroughtPut OBJECT-TYPE
			SYNTAX Integer32
			MAX-ACCESS read-only
			STATUS current
			DESCRIPTION
				"Description. PHY uplink Throught Put"
			::= { cellPerfInfoEntry 2 }

		
		-- 1.3.6.1.4.1.1.2.4.1.1.3
		cellPerfInfoPhyDLThroughtPut OBJECT-TYPE
			SYNTAX Integer32
			MAX-ACCESS read-only
			STATUS current
			DESCRIPTION
				"Description. PHY downlink Throught Put"
			::= { cellPerfInfoEntry 3 }

		
		-- 1.3.6.1.4.1.1.2.4.1.1.4
		cellPerfInfoPhySNMin OBJECT-TYPE
			SYNTAX Integer32
			MAX-ACCESS read-only
			STATUS current
			DESCRIPTION
				"Description. PHY signal/noise minimal value"
			::= { cellPerfInfoEntry 4 }

		
		-- 1.3.6.1.4.1.1.2.4.1.1.5
		cellPerfInfoPhySNMax OBJECT-TYPE
			SYNTAX Integer32
			MAX-ACCESS read-only
			STATUS current
			DESCRIPTION
				"Description. PHY signal/noise maximal value"
			::= { cellPerfInfoEntry 5 }

		
		-- 1.3.6.1.4.1.1.2.4.1.1.6
		cellPerfInfoPhyULVol OBJECT-TYPE
			SYNTAX Counter64
			MAX-ACCESS read-only
			STATUS current
			DESCRIPTION
				"Description. PHY uplink volume date"
			::= { cellPerfInfoEntry 6 }

		
		-- 1.3.6.1.4.1.1.2.4.1.1.7
		cellPerfInfoPhyDLVol OBJECT-TYPE
			SYNTAX Counter64
			MAX-ACCESS read-only
			STATUS current
			DESCRIPTION
				"Description. PHY downlink volume date"
			::= { cellPerfInfoEntry 7 }

		
		-- 1.3.6.1.4.1.1.2.4.1.1.8
		cellPerfInfoMacULRate OBJECT-TYPE
			SYNTAX Counter64
			MAX-ACCESS read-only
			STATUS current
			DESCRIPTION
				"Description."
			::= { cellPerfInfoEntry 8 }

		
		-- 1.3.6.1.4.1.1.2.4.1.1.9
		cellPerfInfoMacDLRate OBJECT-TYPE
			SYNTAX Counter64
			MAX-ACCESS read-only
			STATUS current
			DESCRIPTION
				"Description."
			::= { cellPerfInfoEntry 9 }

		
		-- 1.3.6.1.4.1.1.2.4.1.1.10
		cellPerfInfoRlcULRate OBJECT-TYPE
			SYNTAX Counter64
			MAX-ACCESS read-only
			STATUS current
			DESCRIPTION
				"Description."
			::= { cellPerfInfoEntry 10 }

		
		-- 1.3.6.1.4.1.1.2.4.1.1.11
		cellPerfInfoRlcDLRate OBJECT-TYPE
			SYNTAX Counter64
			MAX-ACCESS read-only
			STATUS current
			DESCRIPTION
				"Description."
			::= { cellPerfInfoEntry 11 }

		
		-- 1.3.6.1.4.1.1.2.4.1.1.12
		cellPerfInfoRlcBufData OBJECT-TYPE
			SYNTAX Integer32
			MAX-ACCESS read-only
			STATUS current
			DESCRIPTION
				"Description."
			::= { cellPerfInfoEntry 12 }

		
		-- 1.3.6.1.4.1.1.2.4.1.1.13
		cellPerfInfoPdcpULRate OBJECT-TYPE
			SYNTAX Counter64
			MAX-ACCESS read-only
			STATUS current
			DESCRIPTION
				"Description."
			::= { cellPerfInfoEntry 13 }

		
		-- 1.3.6.1.4.1.1.2.4.1.1.14
		cellPerfInfoPdcpDLRate OBJECT-TYPE
			SYNTAX Counter64
			MAX-ACCESS read-only
			STATUS current
			DESCRIPTION
				"Description."
			::= { cellPerfInfoEntry 14 }

		
		-- 1.3.6.1.4.1.1.2.4.1.1.15
		cellPerfInfoErrBlkRate OBJECT-TYPE
			SYNTAX Integer32
			MAX-ACCESS read-only
			STATUS current
			DESCRIPTION
				"Description."
			::= { cellPerfInfoEntry 15 }

		
		-- 1.3.6.1.4.1.1.2.4.1.1.16
		cellPerfInfoBandwidthOccupancy OBJECT-TYPE
			SYNTAX Integer32
			MAX-ACCESS read-only
			STATUS current
			DESCRIPTION
				"Description."
			::= { cellPerfInfoEntry 16 }

		
		-- 1.3.6.1.4.1.1.2.4.1.1.17
		cellPerfInfoUEOns OBJECT-TYPE
			SYNTAX Integer32
			MAX-ACCESS read-only
			STATUS current
			DESCRIPTION
				"Description."
			::= { cellPerfInfoEntry 17 }

		
		-- 1.3.6.1.4.1.1.2.4.1.1.18
		cellPerfInfoUEOffs OBJECT-TYPE
			SYNTAX Integer32
			MAX-ACCESS read-only
			STATUS current
			DESCRIPTION
				"Description."
			::= { cellPerfInfoEntry 18 }

		
		-- 1.3.6.1.4.1.1.2.4.1.1.19
		cellPerfInfoUEAccessSuccRate OBJECT-TYPE
			SYNTAX Integer32
			MAX-ACCESS read-only
			STATUS current
			DESCRIPTION
				"Description."
			::= { cellPerfInfoEntry 19 }

		
--  1.3.6.1.4.1.1.2.5
		-- 1.3.6.1.4.1.1.2.5
		trapGroup OBJECT IDENTIFIER ::= { jtsranMIB 5 }

		
--  1.3.6.1.4.1.1.2.5.1
		-- 1.3.6.1.4.1.1.2.5.1
		jtsranNotifications OBJECT IDENTIFIER ::= { trapGroup 1 }

		
--  1.3.6.1.4.1.1.2.5.1.1
		-- 1.3.6.1.4.1.1.2.5.1.1
		jtsranAlarmNotification NOTIFICATION-TYPE
			OBJECTS { trapSeqNum, trapSrc, trapSrcName, trapType, trapId, 
				trapPriority, trapCorrelationId, trapLevel, trapOccurTime, trapAdditionalText
				 }
			STATUS current
			DESCRIPTION 
				"Description."
			::= { jtsranNotifications 1 }

		
--  1.3.6.1.4.1.1.2.5.1.2
		-- 1.3.6.1.4.1.1.2.5.1.2
		jtsranEventNotification NOTIFICATION-TYPE
			OBJECTS { trapSeqNum, trapSrc, trapSrcName, trapType, trapId, 
				trapPriority, trapLevel, trapOccurTime, trapAdditionalText }
			STATUS current
			DESCRIPTION 
				"Description."
			::= { jtsranNotifications 2 }

		
--  1.3.6.1.4.1.1.2.5.2
		-- 1.3.6.1.4.1.1.2.5.2
		jtsranTrapObjects OBJECT IDENTIFIER ::= { trapGroup 2 }

		
--  1.3.6.1.4.1.1.2.5.2.1
		-- 1.3.6.1.4.1.1.2.5.2.1
		trapSeqNum OBJECT-TYPE
			SYNTAX JtSranAlarmSeqNum
			MAX-ACCESS accessible-for-notify
			STATUS current
			DESCRIPTION
				"
				告警/事件序号,与表中索引相同 "
			::= { jtsranTrapObjects 1 }

		
--  1.3.6.1.4.1.1.2.5.2.2
		-- 1.3.6.1.4.1.1.2.5.2.2
		trapSrc OBJECT-TYPE
			SYNTAX JtSranAlarmSrc
			MAX-ACCESS accessible-for-notify
			STATUS current
			DESCRIPTION
				"
				告警/事件源ID "
			::= { jtsranTrapObjects 2 }

		
--  1.3.6.1.4.1.1.2.5.2.3
		-- 1.3.6.1.4.1.1.2.5.2.3
		trapSrcName OBJECT-TYPE
			SYNTAX DisplayString
			MAX-ACCESS accessible-for-notify
			STATUS current
			DESCRIPTION
				"Description."
			::= { jtsranTrapObjects 3 }

		
--  1.3.6.1.4.1.1.2.5.2.4
		-- 1.3.6.1.4.1.1.2.5.2.4
		trapType OBJECT-TYPE
			SYNTAX Integer32
			MAX-ACCESS accessible-for-notify
			STATUS current
			DESCRIPTION
				"
				告警/事件类型 "
			::= { jtsranTrapObjects 4 }

		
--  1.3.6.1.4.1.1.2.5.2.5
		-- 1.3.6.1.4.1.1.2.5.2.5
		trapId OBJECT-TYPE
			SYNTAX Integer32
			MAX-ACCESS accessible-for-notify
			STATUS current
			DESCRIPTION
				"告警/事件ID"
			::= { jtsranTrapObjects 5 }

		
--  1.3.6.1.4.1.1.2.5.2.6
		-- 1.3.6.1.4.1.1.2.5.2.6
		trapPriority OBJECT-TYPE
			SYNTAX JtSranAlarmPriority
			MAX-ACCESS accessible-for-notify
			STATUS current
			DESCRIPTION
				"Description."
			::= { jtsranTrapObjects 6 }

		
--  1.3.6.1.4.1.1.2.5.2.7
		-- 1.3.6.1.4.1.1.2.5.2.7
		trapCorrelationId OBJECT-TYPE
			SYNTAX Integer32
			MAX-ACCESS accessible-for-notify
			STATUS current
			DESCRIPTION
				"伙伴告警ID，告警清除时填入伙伴告警，告警上报时填0"
			::= { jtsranTrapObjects 7 }

		
--  1.3.6.1.4.1.1.2.5.2.8
		-- 1.3.6.1.4.1.1.2.5.2.8
		trapLevel OBJECT-TYPE
			SYNTAX JtSranAlarmLevel
			MAX-ACCESS accessible-for-notify
			STATUS current
			DESCRIPTION
				"Description."
			::= { jtsranTrapObjects 8 }

		
--  1.3.6.1.4.1.1.2.5.2.9
		-- 1.3.6.1.4.1.1.2.5.2.9
		trapOccurTime OBJECT-TYPE
			SYNTAX DateAndTime
			MAX-ACCESS accessible-for-notify
			STATUS current
			DESCRIPTION
				"告警/事件发生的时间"
			::= { jtsranTrapObjects 9 }

		
--  1.3.6.1.4.1.1.2.5.2.10
		-- 1.3.6.1.4.1.1.2.5.2.10
		trapAdditionalText OBJECT-TYPE
			SYNTAX DisplayString
			MAX-ACCESS accessible-for-notify
			STATUS current
			DESCRIPTION
				"告警/事件附加信息"
			::= { jtsranTrapObjects 10 }

		
--  1.3.6.1.4.1.1.2.7
		-- 1.3.6.1.4.1.1.2.7
		alarmGroup OBJECT IDENTIFIER ::= { jtsranMIB 7 }

		
--  1.3.6.1.4.1.1.2.7.1
		-- 1.3.6.1.4.1.1.2.7.1
		alarmConfig OBJECT IDENTIFIER ::= { alarmGroup 1 }

		
--  1.3.6.1.4.1.1.2.7.1.1
		-- 1.3.6.1.4.1.1.2.7.1.1
		activeAlarmMaxRecord OBJECT-TYPE
			SYNTAX Integer32
			MAX-ACCESS read-only
			STATUS current
			DESCRIPTION
				"当前告警最大条数，超过后告警上报会失败"
			::= { alarmConfig 1 }

		
--  1.3.6.1.4.1.1.2.7.1.2
		-- 1.3.6.1.4.1.1.2.7.1.2
		historyAlarmMaxRecord OBJECT-TYPE
			SYNTAX Integer32
			MAX-ACCESS read-only
			STATUS current
			DESCRIPTION
				"历史告警最大条数，超过后将滚动覆盖"
			::= { alarmConfig 2 }

		
--  1.3.6.1.4.1.1.2.7.1.3
		-- 1.3.6.1.4.1.1.2.7.1.3
		eventMaxRecord OBJECT-TYPE
			SYNTAX Integer32
			MAX-ACCESS read-only
			STATUS current
			DESCRIPTION
				"事件最大条数，超过后将滚动覆盖"
			::= { alarmConfig 3 }

		
--  1.3.6.1.4.1.1.2.7.2
		-- 1.3.6.1.4.1.1.2.7.2
		activeAlarmTable OBJECT-TYPE
			SYNTAX SEQUENCE OF ActiveAlarmEntry
			MAX-ACCESS not-accessible
			STATUS current
			DESCRIPTION
				"Description."
			::= { alarmGroup 2 }

		
--  1.3.6.1.4.1.1.2.7.2.1
		-- 1.3.6.1.4.1.1.2.7.2.1
		activeAlarmEntry OBJECT-TYPE
			SYNTAX ActiveAlarmEntry
			MAX-ACCESS not-accessible
			STATUS current
			DESCRIPTION
				"Description."
			INDEX { activeAlarmSeqNum }
			::= { activeAlarmTable 1 }

		
		ActiveAlarmEntry ::=
			SEQUENCE { 
				activeAlarmSeqNum
					JtSranAlarmSeqNum,
				activeAlarmSrc
					JtSranAlarmSrc,
				activeAlarmSrcName
					DisplayString,
				activeAlarmType
					Integer32,
				activeAlarmId
					Integer32,
				activePriority
					JtSranAlarmPriority,
				activeAlarmLevel
					JtSranAlarmLevel,
				activeAlarmOccurTime
					DateAndTime,
				activeAlarmAdditionalText
					DisplayString
			 }

--  1.3.6.1.4.1.1.2.7.2.1.1
		-- 1.3.6.1.4.1.1.2.7.2.1.1
		activeAlarmSeqNum OBJECT-TYPE
			SYNTAX JtSranAlarmSeqNum
			MAX-ACCESS not-accessible
			STATUS current
			DESCRIPTION
				"当前告警序号"
			::= { activeAlarmEntry 1 }

		
--  1.3.6.1.4.1.1.2.7.2.1.2
		-- 1.3.6.1.4.1.1.2.7.2.1.2
		activeAlarmSrc OBJECT-TYPE
			SYNTAX JtSranAlarmSrc
			MAX-ACCESS read-only
			STATUS current
			DESCRIPTION
				"告警源ID"
			::= { activeAlarmEntry 2 }

		
--  1.3.6.1.4.1.1.2.7.2.1.3
		-- 1.3.6.1.4.1.1.2.7.2.1.3
		activeAlarmSrcName OBJECT-TYPE
			SYNTAX DisplayString
			MAX-ACCESS read-only
			STATUS current
			DESCRIPTION
				"告警设备名称"
			::= { activeAlarmEntry 3 }

		
--  1.3.6.1.4.1.1.2.7.2.1.4
		-- 1.3.6.1.4.1.1.2.7.2.1.4
		activeAlarmType OBJECT-TYPE
			SYNTAX Integer32
			MAX-ACCESS read-only
			STATUS current
			DESCRIPTION
				"告警类型"
			::= { activeAlarmEntry 4 }

		
--  1.3.6.1.4.1.1.2.7.2.1.5
		-- 1.3.6.1.4.1.1.2.7.2.1.5
		activeAlarmId OBJECT-TYPE
			SYNTAX Integer32
			MAX-ACCESS read-only
			STATUS current
			DESCRIPTION
				"告警ID"
			::= { activeAlarmEntry 5 }

		
--  1.3.6.1.4.1.1.2.7.2.1.6
		-- 1.3.6.1.4.1.1.2.7.2.1.6
		activePriority OBJECT-TYPE
			SYNTAX JtSranAlarmPriority
			MAX-ACCESS read-only
			STATUS current
			DESCRIPTION
				"告警优先级"
			::= { activeAlarmEntry 6 }

		
--  1.3.6.1.4.1.1.2.7.2.1.7
		-- 1.3.6.1.4.1.1.2.7.2.1.7
		activeAlarmLevel OBJECT-TYPE
			SYNTAX JtSranAlarmLevel
			MAX-ACCESS read-only
			STATUS current
			DESCRIPTION
				"告警等级"
			::= { activeAlarmEntry 7 }

		
--  1.3.6.1.4.1.1.2.7.2.1.8
		-- 1.3.6.1.4.1.1.2.7.2.1.8
		activeAlarmOccurTime OBJECT-TYPE
			SYNTAX DateAndTime
			MAX-ACCESS read-only
			STATUS current
			DESCRIPTION
				"告警发生的时间"
			::= { activeAlarmEntry 8 }

		
--  1.3.6.1.4.1.1.2.7.2.1.9
		-- 1.3.6.1.4.1.1.2.7.2.1.9
		activeAlarmAdditionalText OBJECT-TYPE
			SYNTAX DisplayString
			MAX-ACCESS read-only
			STATUS current
			DESCRIPTION
				"告警附加信息"
			::= { activeAlarmEntry 9 }

		
--  1.3.6.1.4.1.1.2.7.3
		-- 1.3.6.1.4.1.1.2.7.3
		historyAlarmTable OBJECT-TYPE
			SYNTAX SEQUENCE OF HistoryAlarmEntry
			MAX-ACCESS not-accessible
			STATUS current
			DESCRIPTION
				"Description."
			::= { alarmGroup 3 }

		
--  1.3.6.1.4.1.1.2.7.3.1
		-- 1.3.6.1.4.1.1.2.7.3.1
		historyAlarmEntry OBJECT-TYPE
			SYNTAX HistoryAlarmEntry
			MAX-ACCESS not-accessible
			STATUS current
			DESCRIPTION
				"Description."
			INDEX { historyAlarmSeqNum }
			::= { historyAlarmTable 1 }

		
		HistoryAlarmEntry ::=
			SEQUENCE { 
				historyAlarmSeqNum
					JtSranAlarmSeqNum,
				historyAlarmSrc
					JtSranAlarmSrc,
				historyAlarmSrcName
					DisplayString,
				historyAlarmType
					Integer32,
				historyAlarmId
					Integer32,
				historyPriority
					JtSranAlarmPriority,
				historyAlarmLevel
					JtSranAlarmLevel,
				historyAlarmOccurTime
					DateAndTime,
				historyAlarmclearTime
					DateAndTime,
				historyAlarmAdditionalText
					DisplayString
			 }

--  1.3.6.1.4.1.1.2.7.3.1.1
		-- 1.3.6.1.4.1.1.2.7.3.1.1
		historyAlarmSeqNum OBJECT-TYPE
			SYNTAX JtSranAlarmSeqNum
			MAX-ACCESS not-accessible
			STATUS current
			DESCRIPTION
				"历史告警序号"
			::= { historyAlarmEntry 1 }

		
--  1.3.6.1.4.1.1.2.7.3.1.2
		-- 1.3.6.1.4.1.1.2.7.3.1.2
		historyAlarmSrc OBJECT-TYPE
			SYNTAX JtSranAlarmSrc
			MAX-ACCESS read-only
			STATUS current
			DESCRIPTION
				"告警源ID"
			::= { historyAlarmEntry 2 }

		
--  1.3.6.1.4.1.1.2.7.3.1.3
		-- 1.3.6.1.4.1.1.2.7.3.1.3
		historyAlarmSrcName OBJECT-TYPE
			SYNTAX DisplayString
			MAX-ACCESS read-only
			STATUS current
			DESCRIPTION
				"告警设备名称"
			::= { historyAlarmEntry 3 }

		
--  1.3.6.1.4.1.1.2.7.3.1.4
		-- 1.3.6.1.4.1.1.2.7.3.1.4
		historyAlarmType OBJECT-TYPE
			SYNTAX Integer32
			MAX-ACCESS read-only
			STATUS current
			DESCRIPTION
				"告警类型"
			::= { historyAlarmEntry 4 }

		
--  1.3.6.1.4.1.1.2.7.3.1.5
		-- 1.3.6.1.4.1.1.2.7.3.1.5
		historyAlarmId OBJECT-TYPE
			SYNTAX Integer32
			MAX-ACCESS read-only
			STATUS current
			DESCRIPTION
				"告警ID"
			::= { historyAlarmEntry 5 }

		
--  1.3.6.1.4.1.1.2.7.3.1.6
		-- 1.3.6.1.4.1.1.2.7.3.1.6
		historyPriority OBJECT-TYPE
			SYNTAX JtSranAlarmPriority
			MAX-ACCESS read-only
			STATUS current
			DESCRIPTION
				"告警优先级"
			::= { historyAlarmEntry 6 }

		
--  1.3.6.1.4.1.1.2.7.3.1.7
		-- 1.3.6.1.4.1.1.2.7.3.1.7
		historyAlarmLevel OBJECT-TYPE
			SYNTAX JtSranAlarmLevel
			MAX-ACCESS read-only
			STATUS current
			DESCRIPTION
				"告警等级"
			::= { historyAlarmEntry 7 }

		
--  1.3.6.1.4.1.1.2.7.3.1.8
		-- 1.3.6.1.4.1.1.2.7.3.1.8
		historyAlarmOccurTime OBJECT-TYPE
			SYNTAX DateAndTime
			MAX-ACCESS read-only
			STATUS current
			DESCRIPTION
				"告警发生的时间"
			::= { historyAlarmEntry 8 }

		
--  1.3.6.1.4.1.1.2.7.3.1.9
		-- 1.3.6.1.4.1.1.2.7.3.1.9
		historyAlarmclearTime OBJECT-TYPE
			SYNTAX DateAndTime
			MAX-ACCESS read-only
			STATUS current
			DESCRIPTION
				"告警清除的时间"
			::= { historyAlarmEntry 9 }

		
--  1.3.6.1.4.1.1.2.7.3.1.10
		-- 1.3.6.1.4.1.1.2.7.3.1.10
		historyAlarmAdditionalText OBJECT-TYPE
			SYNTAX DisplayString
			MAX-ACCESS read-only
			STATUS current
			DESCRIPTION
				"告警附加信息"
			::= { historyAlarmEntry 10 }

		
--  1.3.6.1.4.1.1.2.7.4
		-- 1.3.6.1.4.1.1.2.7.4
		eventTable OBJECT-TYPE
			SYNTAX SEQUENCE OF EventEntry
			MAX-ACCESS not-accessible
			STATUS current
			DESCRIPTION
				"Description."
			::= { alarmGroup 4 }

		
--  1.3.6.1.4.1.1.2.7.4.1
		-- 1.3.6.1.4.1.1.2.7.4.1
		eventEntry OBJECT-TYPE
			SYNTAX EventEntry
			MAX-ACCESS not-accessible
			STATUS current
			DESCRIPTION
				"Description."
			INDEX { eventSeqNum }
			::= { eventTable 1 }

		
		EventEntry ::=
			SEQUENCE { 
				eventSeqNum
					JtSranAlarmSeqNum,
				eventAlarmSrc
					JtSranAlarmSrc,
				eventSrcName
					DisplayString,
				eventAlarmType
					Integer32,
				eventId
					Integer32,
				eventPriority
					JtSranAlarmPriority,
				eventOccurTime
					DateAndTime,
				eventAdditionalText
					DisplayString
			 }

--  1.3.6.1.4.1.1.2.7.4.1.1
		-- 1.3.6.1.4.1.1.2.7.4.1.1
		eventSeqNum OBJECT-TYPE
			SYNTAX JtSranAlarmSeqNum
			MAX-ACCESS not-accessible
			STATUS current
			DESCRIPTION
				"事件序号"
			::= { eventEntry 1 }

		
--  1.3.6.1.4.1.1.2.7.4.1.2
		-- 1.3.6.1.4.1.1.2.7.4.1.2
		eventAlarmSrc OBJECT-TYPE
			SYNTAX JtSranAlarmSrc
			MAX-ACCESS read-only
			STATUS current
			DESCRIPTION
				"事件源ID"
			::= { eventEntry 2 }

		
--  1.3.6.1.4.1.1.2.7.4.1.3
		-- 1.3.6.1.4.1.1.2.7.4.1.3
		eventSrcName OBJECT-TYPE
			SYNTAX DisplayString
			MAX-ACCESS read-only
			STATUS current
			DESCRIPTION
				"事件设备名称"
			::= { eventEntry 3 }

		
--  1.3.6.1.4.1.1.2.7.4.1.4
		-- 1.3.6.1.4.1.1.2.7.4.1.4
		eventAlarmType OBJECT-TYPE
			SYNTAX Integer32
			MAX-ACCESS read-only
			STATUS current
			DESCRIPTION
				"事件类型"
			::= { eventEntry 4 }

		
--  1.3.6.1.4.1.1.2.7.4.1.5
		-- 1.3.6.1.4.1.1.2.7.4.1.5
		eventId OBJECT-TYPE
			SYNTAX Integer32
			MAX-ACCESS read-only
			STATUS current
			DESCRIPTION
				"事件ID"
			::= { eventEntry 5 }

		
--  1.3.6.1.4.1.1.2.7.4.1.6
		-- 1.3.6.1.4.1.1.2.7.4.1.6
		eventPriority OBJECT-TYPE
			SYNTAX JtSranAlarmPriority
			MAX-ACCESS read-only
			STATUS current
			DESCRIPTION
				"事件优先级"
			::= { eventEntry 6 }

		
--  1.3.6.1.4.1.1.2.7.4.1.7
		-- 1.3.6.1.4.1.1.2.7.4.1.7
		eventOccurTime OBJECT-TYPE
			SYNTAX DateAndTime
			MAX-ACCESS read-only
			STATUS current
			DESCRIPTION
				"事件发生的时间"
			::= { eventEntry 7 }

		
--  1.3.6.1.4.1.1.2.7.4.1.8
		-- 1.3.6.1.4.1.1.2.7.4.1.8
		eventAdditionalText OBJECT-TYPE
			SYNTAX DisplayString
			MAX-ACCESS read-only
			STATUS current
			DESCRIPTION
				"事件附加信息"
			::= { eventEntry 8 }

		
--  1.3.6.1.4.1.1.3
		-- 1.3.6.1.4.1.1.3
		test OBJECT IDENTIFIER ::= { sylincom 3 }

		
--  1.3.6.1.4.1.1.3.1
		-- 1.3.6.1.4.1.1.3.1
		node1 OBJECT-TYPE
			SYNTAX DateAndTime
			MAX-ACCESS read-write
			STATUS current
			DESCRIPTION
				"Description."
			::= { test 1 }

		
--  1.3.6.1.4.1.1.3.2
		-- 1.3.6.1.4.1.1.3.2
		node2 OBJECT-TYPE
			SYNTAX MacAddress
			MAX-ACCESS read-write
			STATUS current
			DESCRIPTION
				"Description."
			::= { test 2 }

		
--  1.3.6.1.4.1.1.3.3
		-- 1.3.6.1.4.1.1.3.3
		node3 OBJECT-TYPE
			SYNTAX RowStatus
			MAX-ACCESS read-write
			STATUS current
			DESCRIPTION
				"Description."
			::= { test 3 }

		
--  1.3.6.1.4.1.1.3.4
		-- 1.3.6.1.4.1.1.3.4
		node4 OBJECT-TYPE
			SYNTAX TruthValue
			MAX-ACCESS read-write
			STATUS current
			DESCRIPTION
				"Description."
			::= { test 4 }

		
--  1.3.6.1.4.1.1.3.5
		-- 1.3.6.1.4.1.1.3.5
		node5 OBJECT-TYPE
			SYNTAX DisplayString
			MAX-ACCESS read-write
			STATUS current
			DESCRIPTION
				"Description."
			::= { test 5 }

		
	
	END

--
-- SYLINCOM-MIB.my
--
